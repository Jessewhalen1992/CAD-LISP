(command "NETLOAD""C:/AUTOCAD-SETUP CG/CG_LISP/UTMCHECKCLOSE.dll")
(command "NETLOAD""C:/AUTOCAD-SETUP CG/CG_LISP/UTMSAVEAS.dll")
(command "NETLOAD""C:/AUTOCAD-SETUP CG/CG_LISP/SECTIONGENERATOR.dll")
(command "NETLOAD""C:/AUTOCAD-SETUP CG/CG_LISP/NewBearingDistanceProgram2025.DLL")
(command "NETLOAD""C:/AUTOCAD-SETUP CG/CG_LISP/WORKSPACE PROGRAM/MyAutocadProgram.DLL")
