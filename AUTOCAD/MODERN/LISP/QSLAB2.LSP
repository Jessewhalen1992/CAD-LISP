;The QSLAB2 function

(defun c:QSLAB2 ()
(setq oldtxt (getvar"textstyle"))
(setq oldlay (getvar"clayer"))

(prompt "\nPick the quarter section label ... ")
(setq ent (car (entsel)))
(setq inspt (cdr (assoc 10 (entget ent))))
(setq x1 (car inspt))
(setq y1 (cadr inspt))
(setq ent2 (entnext ent))
(if (and (= (cdr (assoc 0 (entget ent2))) "ATTRIB") (= (cdr (assoc 2 (entget ent2))) "SEC"))
  (setq sec (cdr (assoc 1 (entget ent2))))
)
(setq ent3 (entnext ent2))
(if (and (= (cdr (assoc 0 (entget ent3))) "ATTRIB") (= (cdr (assoc 2 (entget ent3))) "TWP"))
  (setq twp (cdr (assoc 1 (entget ent3))))
)
(setq ent4 (entnext ent3))
(if (and (= (cdr (assoc 0 (entget ent4))) "ATTRIB") (= (cdr (assoc 2 (entget ent4))) "RGE"))
  (setq rge (cdr (assoc 1 (entget ent4))))
)
(setq ent5 (entnext ent4))
(if (and (= (cdr (assoc 0 (entget ent5))) "ATTRIB") (= (cdr (assoc 2 (entget ent5))) "MER"))
  (setq mer (cdr (assoc 1 (entget ent5))))
)
(setq qtrpt (getpoint "\nPick a point in the quarter ... "))
(setq x2 (car qtrpt))
(setq y2 (cadr qtrpt))
(if (and (< x2 x1) (> y2 y1))
  (setq qtr "N.W.")
)
(if (and (> x2 x1) (> y2 y1))
  (setq qtr "N.E.")
)
(if (and (< x2 x1) (< y2 y1))
  (setq qtr "S.W.")
)
(if (and (> x2 x1) (< y2 y1))
  (setq qtr "S.E.")
)

(setvar "clayer" "C-symbol")
(setq qstxt (strcat "Theor. " qtr "1/4 Sec. " sec "-" twp "-" rge "-" "W." mer "M."))
(setvar "cecolor" "green")
(setvar"textstyle" "175l")
(command "text" "j" "bc" qtrpt "90" qstxt) 


(setvar"cecolor" "bylayer")
(setvar"textstyle" oldtxt)
(setvar"clayer" oldlay)
(setvar "cmdecho" 1)
(princ)
)
