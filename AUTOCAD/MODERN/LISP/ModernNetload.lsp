(command "NETLOAD""C:/AUTOCAD-SETUP CG/CG_LISP/AUTO UPDATE LABELS/UpdateDimLabels.DLL")
(command "NETLOAD""C:/AUTOCAD-SETUP CG/CG_LISP/DRILL PROPERTIES/Drill Namer.dll")
(command "NETLOAD""C:/AUTOCAD-SETUP CG/CG_LISP/DRILL PROPERTIES/WORKSPACE PROGRAM/MyAutocadProgram.dll")
(command "NETLOAD""C:/AUTOCAD-SETUP CG/CG_LISP/NewBearingDistanceProgram2025.DLL")
